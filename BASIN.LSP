; -----------------------------------------------------------------------------
; BASIN.LSP  –  Interior Contour Generator for Retention Basins
; -----------------------------------------------------------------------------
; Compatible with Autodesk Civil 3D 2021, 2022, 2023, 2024 (vanilla AutoLISP/VLISP)
; -----------------------------------------------------------------------------
; INSTALLATION
;   • Copy BASIN.LSP to any folder that is in AutoCAD’s support search path, or
;     load it manually with APPLOAD.
;   • After loading, type BASIN at the command line.
;
; WORKFLOW
;   1. Draw a single, closed 2D polyline at the desired elevation representing
;      the top‑of‑berm.
;   2. Type BASIN.
;   3. Respond to the prompts for total basin depth, the horizontal side‑slope
;      ratio, and the vertical contour interval (defaults = 6.0, 3.0 H:1V, 1.0).
;   4. The routine creates a layer named **BASIN_CONTOURS** (white, thawed, on)
;      and offsets the selected polyline inward the correct horizontal distance
;      for each contour, assigning the appropriate elevation to every new
;      polyline.  A summary of how many interior contours were created is
;      reported on completion.
;
; AUTHOR / DATE
;   Generated by ChatGPT – June 19 2025
; -----------------------------------------------------------------------------
; Change history
;   2025‑06‑19  Initial release
; -----------------------------------------------------------------------------
;
; --------  GLOBALS ------------------------------------------------------------

(setq *BASIN‑Layer* "BASIN_CONTOURS")

; --------  HELPERS ------------------------------------------------------------

(defun Basin‑MakeLayer (name color / doc layers lay)
  "Create (or retrieve) layer NAME and set its color index to COLOR.
   Returns NAME."
  (setq doc    (vla-get-ActiveDocument (vlax-get-Acad-Object))
        layers (vla-get-Layers doc))
  (if (not (tblsearch "LAYER" name))
    (progn
      (setq lay (vla-Add layers name))
      (vla-put-Color lay color)))
  name)

(defun Basin‑InwardSign (pl dist / v saf lst off area0 area1)
  "Determine the sign (±1) required to offset PL inward.
   Tests a small positive distance DIST; if the resulting area is smaller it
   is inward (sign = +1), otherwise outward (sign = ‑1).  The test offset is
   deleted."
  (setq v   (vla-Offset pl dist)
        saf (vlax-safearray->list v)
        off (car saf)
        area0 (vla-get-Area pl)
        area1 (vla-get-Area off))
  (vla-Delete off)
  (if (< area1 area0) 1.0 -1.0))

(defun Basin‑UndoStart ()  (vla-StartUndoMark (vla-get-ActiveDocument (vlax-get-Acad-Object))))
(defun Basin‑UndoEnd   ()  (vla-EndUndoMark   (vla-get-ActiveDocument (vlax-get-Acad-Object))))

; --------  ERROR HANDLER ------------------------------------------------------

(defun Basin‑Error (msg)
  (if (and msg (/= msg "Function cancelled"))
    (princ (strcat "\n*Error* " msg)))
  (Basin‑UndoEnd)
  (if *BASIN‑OldCMDECHO* (setvar 'CMDECHO *BASIN‑OldCMDECHO*))
  (setq *error* *BASIN‑OldError*)
  (princ))

; --------  MAIN COMMAND -------------------------------------------------------

(defun c:BASIN (/ *BASIN‑OldError* *BASIN‑OldCMDECHO*
                   depth slope interval ent pl sign nSteps step
                   offDist var lst offObj cnt elev layerName)
  (princ "\n--- BASIN – Interior Contour Generator ---")
  (setq *BASIN‑OldError* *error*
        *BASIN‑OldCMDECHO* (getvar 'CMDECHO))
  (setq *error*     Basin‑Error)
  (setvar 'CMDECHO 0)
  (Basin‑UndoStart)

  ;; ---- User input -----------------------------------------------------------
  (setq depth    (getreal "\nTotal basin depth <6.0>: "))
  (if (null depth) (setq depth 6.0))
  (setq slope    (getreal "\nHorizontal side‑slope ratio <3.0>: "))
  (if (null slope) (setq slope 3.0))
  (setq interval (getreal "\nVertical contour interval <1.0>: "))
  (if (null interval) (setq interval 1.0))

  (prompt "\nSelect closed 2D polyline representing top‑of‑berm: ")
  (setq ent (car (entsel)))
  (if (null ent)
    (progn (prompt "\nNothing selected.") (Basin‑UndoEnd) (exit)))
  (setq pl (vlax-ename->vla-object ent))
  (if (/= (vla-get-ObjectName pl) "AcDbPolyline")
    (progn (prompt "\nSelected entity is not an AcDbPolyline.") (Basin‑UndoEnd) (exit)))

  ;; ---- Setup ----------------------------------------------------------------
  (setq sign        (Basin‑InwardSign pl (* slope interval))
        layerName   (Basin‑MakeLayer *BASIN‑Layer* 7)
        elev        (vla-get-Elevation pl)
        nSteps      (fix (/ depth interval))
        cnt         0
        step        1)

  ;; ---- Loop through each interior contour ----------------------------------
  (while (<= step nSteps)
    (setq offDist  (* sign slope interval step)
          var      (vl-catch-all-apply 'vla-Offset (list pl offDist)))
    (if (vl-catch-all-error-p var)
      (setq step (1+ nSteps))        ; abort on error
      (progn
        (setq lst (vlax-safearray->list var))
        (if lst
          (foreach offObj lst
            (vla-put-Layer offObj layerName)
            (vla-put-Elevation offObj (- elev (* interval step)))
            (setq cnt (1+ cnt)))
          (setq step (1+ nSteps))))
    (setq step (1+ step)))

  ;; ---- Report ----------------------------------------------------------------
  (prompt (strcat "\nInterior contours created: " (itoa cnt)))

  ;; ---- Cleanup --------------------------------------------------------------
  (Basin‑UndoEnd)
  (setvar 'CMDECHO *BASIN‑OldCMDECHO*)
  (setq *error* *BASIN‑OldError*)
  (princ))

(princ "\nBASIN.LSP loaded – type BASIN to run.")
(princ)
; -----------------------------------------------------------------------------
